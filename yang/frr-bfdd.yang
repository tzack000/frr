// SPDX-License-Identifier: BSD-2-Clause
module frr-bfdd {
  yang-version 1.1;
  namespace "http://frrouting.org/yang/bfdd";
  prefix frr-bfdd;

  import ietf-inet-types {
    prefix inet;
  }
  import ietf-yang-types {
    prefix yang;
  }
  import frr-interface {
    prefix frr-interface;
  }
  import frr-vrf {
    prefix frr-vrf;
  }

  organization "FRRouting";
  contact
    "FRR Users List:       <mailto:frog@lists.frrouting.org>
     FRR Development List: <mailto:dev@lists.frrouting.org>";
  description
    "This module defines a model for managing FRR bfdd daemon.

     Copyright 2025 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2025-03-03 {
    description "Add log-session-changes leaf";
    reference
      "RFC 5880: Bidirectional Forwarding Detection (BFD).
       RFC 5881: Bidirectional Forwarding Detection (BFD)
                 for IPv4 and IPv6 (Single Hop).
       RFC 5883: Bidirectional Forwarding Detection (BFD) for Multihop Paths.";
  }

  revision 2025-01-16 {
    description "Add Micro-BFD over LAG support (RFC 7130)";
    reference
      "RFC 7130: Bidirectional Forwarding Detection (BFD) on
                 Link Aggregation Group (LAG) Interfaces.";
  }

  revision 2019-05-09 {
    description "Initial revision.";
    reference
      "RFC 5880: Bidirectional Forwarding Detection (BFD).
       RFC 5881: Bidirectional Forwarding Detection (BFD)
                 for IPv4 and IPv6 (Single Hop).
       RFC 5883: Bidirectional Forwarding Detection (BFD) for Multihop Paths.";
  }

  /*
   * BFD types declaration.
   */
  typedef multiplier {
    type uint8 {
      range "1..255";
    }
    description "Detection multiplier";
  }

  typedef discriminator {
    type uint32 {
      range "1..4294967295";
    }
    description "BFD session identification";
  }

  typedef state {
    type enumeration {
      enum admin-down {
        value 0;
        description "Administratively down";
      }
      enum down {
        value 1;
        description "Down";
      }
      enum init {
        value 2;
        description "Initializing";
      }
      enum up {
        value 3;
        description "Up";
      }
    }
    description "BFD session state";
  }

  typedef diagnostic {
    type enumeration {
      enum ok {
        value 0;
        description "Ok";
      }
      enum control-expired {
        value 1;
        description "Control timer expired";
      }
      enum echo-failed {
        value 2;
        description "Echo function failed";
      }
      enum neighbor-down {
        value 3;
        description "Neighbor signaled session down";
      }
      enum forwarding-reset {
        value 4;
        description "Forwarding plane reset";
      }
      enum path-down {
        value 5;
        description "Path down";
      }
      enum concatenated-path-down {
        value 6;
        description "Concatenated path down";
      }
      enum administratively-down {
        value 7;
        description "Administratively down";
      }
      enum reverse-concat-path-down {
        value 8;
        description "Reverse concatenated path down";
      }
    }
    description "BFD session diagnostic";
  }

  typedef profile-name {
    type string {
      length "1..64";
    }
    description "Profile name format";
  }

  typedef profile-ref {
    type leafref {
      path "/frr-bfdd:bfdd/frr-bfdd:bfd/frr-bfdd:profile/frr-bfdd:name";
      require-instance false;
    }
    description "Reference to a BFD profile";
  }

  /*
   * Shared BFD items.
   */
  grouping session-common {
    description "Common BFD session settings";

    leaf detection-multiplier {
      type multiplier;
      default 3;
      description "Local session detection multiplier";
    }

    leaf desired-transmission-interval {
      type uint32 {
          range "10000..max";
      }
      units microseconds;
      default 300000;
      description "Minimum desired control packet transmission interval";
    }

    leaf required-receive-interval {
      type uint32 {
          range "10000..max";
      }
      units microseconds;
      default 300000;
      description "Minimum required control packet receive interval";
    }

    leaf administrative-down {
      type boolean;
      default false;
      description "Disables or enables the session administratively";
    }

    leaf passive-mode {
      type boolean;
      default false;
      description
        "Don't attempt to start session establishment.";
    }

    leaf log-session-changes {
      type boolean;
      default false;
      description "Log session changes from/to Up state to/from Down state";
    }

  }

  grouping session-echo {
    description "BFD session echo settings";

    leaf echo-mode {
      type boolean;
      default false;
      description "Use echo packets to detect failures";
    }

    leaf desired-echo-transmission-interval {
      type uint32 {
          range "10000..max";
      }
      units microseconds;
      default 50000;
      description "Minimum desired echo packet transmission interval";
    }

    leaf required-echo-receive-interval {
      type uint32 {
          range "0 | 10000..max";
      }
      units microseconds;
      default 50000;
      description "Minimum required echo packet receive interval";
    }
  }

  grouping session-multi-hop {
    description "BFD session multi hop settings.";

    leaf minimum-ttl {
      type uint8 {
        range "1..254";
      }
      default "254";
      description
        "Minimum expected TTL on received packets.";
    }
  }

  grouping bfd-monitoring {
    description
      "BFD monitoring template for protocol integration.";

    leaf source {
      type inet:ip-address;
      description
        "Source address to use for liveness check.

         When source is not set and multi-hop is `false` the source
         address will be `0.0.0.0` (any).

         When source is not set and multi-hop is `true` the source
         address will be automatic selected through Next Hop Tracking (NHT).";
    }

    leaf multi-hop {
      type boolean;
      default false;
      description
        "Use multi hop session instead of single hop.";
    }

    leaf profile {
      type frr-bfdd:profile-ref;
      description
        "BFD pre configured profile.";
    }
  }

  grouping session-states {
    description
      "This grouping defines the states of a BFD session.";

    /*
     * Local settings.
     */

    leaf local-discriminator {
      type discriminator;
      description "Local session identifier";
    }

    leaf local-state {
      type state;
      description "Local session state";
    }

    leaf local-diagnostic {
      type diagnostic;
      description "Local session diagnostic";
    }

    leaf local-multiplier {
      type multiplier;
      description "Local session current multiplier";
    }

    /*
     * Remote settings.
     */
    leaf remote-discriminator {
      type discriminator;
      description "Remote session identifier";
    }

    leaf remote-state {
      type state;
      description "Remote session state";
    }

    leaf remote-diagnostic {
      type diagnostic;
      description "Local session diagnostic";
    }

    leaf remote-multiplier {
      type multiplier;
      description "Remote session detection multiplier";
    }

    /*
     * Negotiated settings.
     */
    leaf negotiated-transmission-interval {
      type uint32;
      units microseconds;
      description "Negotiated transmit interval";
    }

    leaf negotiated-receive-interval {
      type uint32;
      units microseconds;
      description "Negotiated receive interval";
    }

    leaf detection-mode {
      type enumeration {
        enum async-with-echo {
          value "1";
          description "Async with echo";
        }
        enum async-without-echo {
          value "2";
          description "Async without echo";
        }
        enum demand-with-echo {
          value "3";
          description "Demand with echo";
        }
        enum demand-without-echo {
          value "4";
          description "Demand without echo";
        }
      }
      description "Detection mode";
    }

    /*
     * Statistics.
     */
    leaf last-down-time {
      type yang:date-and-time;
      description "Time and date of the last time session was down";
    }

    leaf last-up-time {
      type yang:date-and-time;
      description "Time and date of the last time session was up";
    }

    leaf session-down-count {
      type uint32;
      description "Number of times the session went down";
    }

    leaf session-up-count {
      type uint32;
      description "Number of times the session went up";
    }

    leaf control-packet-input-count {
      type uint64;
      description "Number of control packets received";
    }

    leaf control-packet-output-count {
      type uint64;
      description "Number of control packets sent";
    }

    /*
     * Echo mode operational data.
     */
    leaf negotiated-echo-transmission-interval {
      type uint32;
      units microseconds;
      description "Negotiated echo transmit interval";
    }

    /*
     * Statistics.
     */
    leaf echo-packet-input-count {
      type uint64;
      description "Number of echo packets received";
    }

    leaf echo-packet-output-count {
      type uint64;
      description "Number of echo packets sent";
    }
  }

  /*
   * Micro-BFD LAG groupings (RFC 7130)
   */
  grouping lag-common {
    description "Common Micro-BFD LAG settings";

    leaf detection-multiplier {
      type multiplier;
      default 3;
      description "Detection multiplier for all member sessions";
    }

    leaf desired-transmission-interval {
      type uint32 {
        range "10000..max";
      }
      units microseconds;
      default 300000;
      description "Minimum desired control packet transmission interval";
    }

    leaf required-receive-interval {
      type uint32 {
        range "10000..max";
      }
      units microseconds;
      default 300000;
      description "Minimum required control packet receive interval";
    }

    leaf administrative-down {
      type boolean;
      default false;
      description "Administratively disable all member sessions";
    }
  }

  grouping lag-member-states {
    description "Operational state for a LAG member BFD session";

    leaf link-up {
      type boolean;
      description "Physical link status of the member interface";
    }

    leaf bfd-up {
      type boolean;
      description "BFD session status on the member interface";
    }

    leaf protodown-set {
      type boolean;
      description "Whether protodown has been set on the interface";
    }

    uses session-states;
  }

  grouping lag-stats {
    description "Aggregate statistics for a LAG";

    leaf total-members {
      type uint8;
      description "Total number of configured member links";
    }

    leaf active-members {
      type uint8;
      description "Number of member links with BFD session Up";
    }

    leaf down-members {
      type uint8;
      description "Number of member links with BFD session Down";
    }
  }

  /*
   * BFD operational.
   */
  container bfdd {
    description
      "This container defines BFD daemon configuration.";

    container bfd {
      presence "Present if the BFD protocol is enabled";

      list profile {
        key "name";
        description "BFD pre configuration profiles";

        leaf name {
          type profile-name;
          description "Profile name";
        }

        uses session-common;
        uses session-echo;
        uses session-multi-hop;
      }

      container sessions {
        description
          "This container provides information about sessions.";

        list single-hop {
          key "dest-addr interface vrf";
          description "List of single hop sessions";

          leaf dest-addr {
            type inet:ip-address;
            description "IP address of the peer";
          }

          leaf interface {
            type frr-interface:interface-ref;
            description "Interface to use to contact peer";
          }

          leaf vrf {
            type frr-vrf:vrf-ref;
            description "Virtual Routing Domain name";
          }

          leaf source-addr {
            type inet:ip-address;
            description "Local IP address";
          }

          leaf profile {
            type profile-ref;
            description "Override defaults with profile.";
          }

          uses session-common;
          uses session-echo;

          container stats {
            uses session-states;
            config false;
            description
              "This container provides statistics for sessions.";
          }
        }

        list multi-hop {
          key "source-addr dest-addr vrf";
          description "List of multi hop sessions";

          leaf source-addr {
            type inet:ip-address;
            description "Local IP address";
          }

          leaf dest-addr {
            type inet:ip-address;
            description "IP address of the peer";
          }

          leaf vrf {
            type frr-vrf:vrf-ref;
            description "Virtual Routing Domain name";
          }

          leaf profile {
            type profile-ref;
            description "Override defaults with profile.";
          }

          uses session-common;
          uses session-multi-hop;

          container stats {
            uses session-states;
            config false;
            description
              "This container provides statistics for sessions.";
          }
        }

        list sbfd-echo {
          key "source-addr bfd-name vrf";
          description "support a special echo SBFD session in RFC7880, and enhanced with SRv6 encapsulation";

          leaf source-addr {
            type inet:ip-address;
            description "Local IP address";
          }

          leaf dest-addr {
            type inet:ip-address;
            description "IP address of the peer";
          }

          leaf bfd-name {
            type string;
            description "Bfd session name.";
          }

          leaf vrf {
            type frr-vrf:vrf-ref;
            description "Virtual Routing Domain name";
          }

          leaf profile {
            type profile-ref;
            description "Override defaults with profile.";
          }

          leaf-list srv6-encap-data {
            type inet:ipv6-address;
            max-elements 6;

            description "segment list ipv6 addresses for srv6 encapsulation";
          }

          leaf srv6-source-ipv6 {
            type inet:ipv6-address;
            description "source ipv6 address for srv6 encapsulation";
          }

          leaf bfd-mode {
            type uint32;
            description "Bfd session mode.";
          }

          leaf multi-hop {
            type boolean;
            description "Use multi hop session instead of single hop.";
          }

          uses session-common;
          uses session-multi-hop;
          uses session-echo;

          container stats {
            uses session-states;
            config false;
            description
              "This container provides statistics for sessions.";
          }
        }

        list sbfd-init {
          key "source-addr dest-addr bfd-name vrf";
          description "support SBFD session in RFC7880, and optional with SRv6 encapsulation";

          leaf source-addr {
            type inet:ip-address;
            description "Local IP address";
          }

          leaf dest-addr {
            type inet:ip-address;
            description "IP address of the peer";
          }

          leaf bfd-name {
            type string;
            description "Bfd session name.";
          }

          leaf vrf {
            type frr-vrf:vrf-ref;
            description "Virtual Routing Domain name";
          }

          leaf profile {
            type profile-ref;
            description "Override defaults with profile.";
          }

          leaf-list srv6-encap-data {
            type inet:ipv6-address;
            max-elements 6;

            description "segment list ipv6 addresses for srv6 encapsulation";
          }

          leaf srv6-source-ipv6 {
            type inet:ip-address;
            description "source ipv6 address for srv6 encapsulation";
          }

          leaf remote-discr {
            type uint32;
            default 0;
            description
              "Remote session identifier";
          }

          leaf bfd-mode {
            type uint32;
            description "Bfd session mode.";
          }

          leaf multi-hop {
            type boolean;
            description "Use multi hop session instead of single hop.";
          }

          uses session-common;
          uses session-multi-hop;

          container stats {
            uses session-states;
            config false;
            description
              "This container provides statistics for sessions.";
          }
        }
      }

      /*
       * Micro-BFD over LAG (RFC 7130)
       */
      list lag {
        key "lag-name vrf";
        description
          "List of Micro-BFD LAG session groups.
           Each LAG can have multiple member links running independent
           BFD sessions per RFC 7130.";

        leaf lag-name {
          type string {
            length "1..15";
          }
          description "LAG interface name (e.g., bond0, PortChannel001)";
        }

        leaf vrf {
          type frr-vrf:vrf-ref;
          description "Virtual Routing Domain name";
        }

        leaf profile {
          type profile-ref;
          description "Apply BFD profile settings to all member sessions";
        }

        uses lag-common;

        list member-link {
          key "name";
          description
            "List of member links in this LAG.
             Each member link runs an independent Micro-BFD session.";

          leaf name {
            type frr-interface:interface-ref;
            description "Member interface name (e.g., eth0, Ethernet0)";
          }

          leaf local-address {
            type inet:ip-address;
            description "Local IP address for BFD session on this member";
          }

          leaf peer-address {
            type inet:ip-address;
            description "Peer IP address for BFD session on this member";
          }

          leaf detection-multiplier {
            type multiplier;
            description
              "Member-specific detection multiplier override.
               If not set, inherits from LAG-level configuration.";
          }

          leaf desired-transmission-interval {
            type uint32 {
              range "10000..max";
            }
            units microseconds;
            description
              "Member-specific transmit interval override.
               If not set, inherits from LAG-level configuration.";
          }

          leaf required-receive-interval {
            type uint32 {
              range "10000..max";
            }
            units microseconds;
            description
              "Member-specific receive interval override.
               If not set, inherits from LAG-level configuration.";
          }

          container stats {
            config false;
            description "Operational state and statistics for this member";

            uses lag-member-states;
          }
        }

        container stats {
          config false;
          description "Aggregate statistics for this LAG";

          uses lag-stats;
        }
      }
      description
        "This container defines BFD protocol configuration.";
    }
  }
}
